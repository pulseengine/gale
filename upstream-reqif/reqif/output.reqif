# Documentation export by StrictDoc

# Specification: C library

## R1 (TEXT)
SPDX-License-Identifier: Apache-2.0

## ZEP-SRS-18-1: Formatted output (REQUIREMENT)
The Zephyr RTOS shall support formatted output.
- STATUS: Draft
- TYPE: Functional
- COMPONENT: C Library
- USER_STORY: As a Zephyr RTOS user, I want to be able to printf with various output formats.
- Parent -> ZEP-SYRS-3

## ZEP-SRS-18-2: Floating Point Math Support (REQUIREMENT)
The Zephyr RTOS shall support floating point math libraries for processors where floating point is available.
- STATUS: Draft
- TYPE: Functional
- COMPONENT: C Library
- USER_STORY: As a Zephyr RTOS user, I want to be able to calculate with floating point numbers.
- Parent -> ZEP-SYRS-3

## ZEP-SRS-18-3: Boolean Primitives Support (REQUIREMENT)
The Zephyr RTOS shall support boolean primitives.
- STATUS: Draft
- TYPE: Functional
- COMPONENT: C Library
- USER_STORY: As a Zephyr RTOS user, I want to be able to work with boolean values and logic.
- Parent -> ZEP-SYRS-3

## ZEP-SRS-18-4: Standard Unix time interface (REQUIREMENT)
The Zephyr RTOS shall support the standard UNIX time interface.
- STATUS: Draft
- TYPE: Functional
- COMPONENT: C Library
- USER_STORY: As a Zephyr User, I want to be able to use system time.
- Parent -> ZEP-SYRS-3

## ZEP-SRS-18-5: Strings support (REQUIREMENT)
The Zephyr RTOS shall support an interface to manage strings.
- STATUS: Draft
- TYPE: Functional
- COMPONENT: C Library
- USER_STORY: As a Zephyr RTOS user, I want to be able to manipulate text strings.
- Parent -> ZEP-SYRS-3

## ZEP-SRS-18-6: Moving/copying regions of memory (REQUIREMENT)
The Zephyr RTOS shall support an interface to move contents between regions of memory.
- STATUS: Draft
- TYPE: Functional
- COMPONENT: C Library
- USER_STORY: As a Zephyr RTOS user, I want to copy the memory contents to different addresses.
- Parent -> ZEP-SYRS-3

## ZEP-SRS-18-7: I/O based interface (REQUIREMENT)
The Zephyr RTOS shall support a file i/O based interface for driver communication.
- STATUS: Draft
- TYPE: Functional
- COMPONENT: C Library
- USER_STORY: As a Zephyr RTOS user, I want to be able to use File I/O functions.
- Parent -> ZEP-SYRS-3

## ZEP-SRS-18-8: C99 integer types (REQUIREMENT)
The Zephyr RTOS shall support standard C99 integer types.
- STATUS: Draft
- TYPE: Functional
- COMPONENT: C Library
- USER_STORY: As a Zephyr RTOS user, I want to be able to calculate with C99 Integers.
- Parent -> ZEP-SYRS-3

## ZEP-SRS-18-9: Standard System Error Numbers (IEEE Std 1003.1-2017) (REQUIREMENT)
The Zephyr RTOS shall support standard system error numbers as defined by IEEE Std 1003.1-2017.
- STATUS: Draft
- TYPE: Functional
- COMPONENT: C Library
- USER_STORY: As a Zephyr RTOS user, I want to be able to use IEE Std 1003.1-2017 Error Numbers for Interoperability.
- Parent -> ZEP-SYRS-3

## ZEP-SRS-18-10: Document set of Zephyr OS required C library functions in Safety Manual (REQUIREMENT)
The set of C Library functions required by Zephyr needs to be documented in the Zephyr Safety Manual.
- STATUS: Draft
- TYPE: Functional
- COMPONENT: C Library
- USER_STORY: As a Zephyr user, I want to know which C library functions are being called by the Zephyr OS safety scope code.
- Parent -> ZEP-SYRS-3

## ZEP-SRS-18-11: Support external C libraries documentation in Zephyr Safety Manual (REQUIREMENT)
The Zephyr Safety Manual needs to specify how to configure the support of external C Libraries.
- STATUS: Draft
- TYPE: Functional
- COMPONENT: C Library
- USER_STORY: As a Zephyr User, I need to understand how to configure the external C libraries to align with the validation that has been performed.
- Parent -> ZEP-SYRS-3

# Specification: Condition Variables

## ZEP-SRS-21-1: Dynamic initialization of condition variables (REQUIREMENT)
The Zephyr RTOS shall provide a mechanism to define and initialize a condition variable dynamically (at runtime).
- STATUS: Draft
- TYPE: Functional
- COMPONENT: Condition Variables
- Parent -> ZEP-SYRS-20

## ZEP-SRS-21-2: Static initialization of condition variables (REQUIREMENT)
The Zephyr RTOS shall provide a mechanism to define and initialize a condition variable statically (at compile time).
- STATUS: Draft
- TYPE: Functional
- COMPONENT: Condition Variables
- Parent -> ZEP-SYRS-20

## ZEP-SRS-21-3: Signal one waiting thread (REQUIREMENT)
The Zephyr RTOS shall provide a mechanism to signal the highest priorite waiting thread when a condition is met.
- STATUS: Draft
- TYPE: Functional
- COMPONENT: Condition Variables
- Parent -> ZEP-SYRS-20

## ZEP-SRS-21-4: Signal multiple waiting threads (REQUIREMENT)
The Zephyr RTOS shall provide a mechanism to signal all waiting threads when a condition is met.
- STATUS: Draft
- TYPE: Functional
- COMPONENT: Condition Variables
- Parent -> ZEP-SYRS-20

## ZEP-SRS-21-5: Wait on a condition variable (REQUIREMENT)
The Zephyr RTOS shall provide a mechanism for a thread to wait on a condition variable.
- STATUS: Draft
- TYPE: Functional
- COMPONENT: Condition Variables
- Parent -> ZEP-SYRS-20

## ZEP-SRS-21-6: Wait timeout on a condition variable (REQUIREMENT)
When waiting on a condition variable, the thread shall specify a timeout value.
- STATUS: Draft
- TYPE: Functional
- COMPONENT: Condition Variables
- Parent -> ZEP-SYRS-20

## ZEP-SRS-21-7: Wait timeout occurence (REQUIREMENT)
When a timeout occurs while waiting on a condition variable, the thread shall be unblocked and a timeout error shall be returned.
- STATUS: Draft
- TYPE: Functional
- COMPONENT: Condition Variables
- Parent -> ZEP-SYRS-20

## ZEP-SRS-21-8: Release mutex on wait (REQUIREMENT)
If a thread is waiting on a condition variable, the thread shall release the current owned mutex independently.
- STATUS: Draft
- TYPE: Functional
- COMPONENT: Condition Variables
- Parent -> ZEP-SYRS-20

## ZEP-SRS-21-9: Unblock a waiting thread (REQUIREMENT)
henever some thread signals a condition variable the Zephyr RTOS shall unblock the highest priority thread currently waiting for this condition variable.
- STATUS: Draft
- TYPE: Functional
- COMPONENT: Condition Variables
- Parent -> ZEP-SYRS-20

# Specification: Data Passing

## R22 (TEXT)
SPDX-License-Identifier: Apache-2.0

## ZEP-SRS-15-1: Traditional FIFO Queue (REQUIREMENT)
The Zephyr RTOS shall provide a kernel object that implements a traditional first in, first out (FIFO) queue, allowing threads and ISRs to add and remove a limited number of 32-bit data values.
- STATUS: Draft
- TYPE: Functional
- COMPONENT: Data Passing
- USER_STORY: As a Zephyr RTOS user I want to be able to exchange 1 to N data objects between different threads and ISR in a thread-safe manner with a first-in-first-out (queue) behaviour.

## ZEP-SRS-15-2: Traditional LIFO queue (REQUIREMENT)
The Zephyr RTOS shall provide a kernel object that implements a traditional last in, first out (LIFO) queue, allowing threads and ISRs to add and remove a limited number of 32-bit data values.
- STATUS: Draft
- TYPE: Functional
- COMPONENT: Data Passing
- USER_STORY: As a Zephyr RTOS user I want to be able to exchange 1 to N data objects between different threads and ISR in a thread-safe manner with a last-in-first-out (stack) behaviour.

# Specification: Device Driver API

## R25 (TEXT)
SPDX-License-Identifier: Apache-2.0

## ZEP-SRS-14-1: Device Driver Abstraction (REQUIREMENT)
The Zephyr RTOS shall provide abstraction of device drivers with common functionalities as an intermediate interface between applications and device drivers, where such interface is implemented by individual device drivers.

Proposal for replacement: Zephyr shall provide an interface between application and individual device drivers to provide an abstraction of device drivers with common functionalities.
- STATUS: Draft
- TYPE: Functional
- COMPONENT: Device Driver API

## ZEP-SRS-14-2: Expose kernel to hardware interrupts (REQUIREMENT)
The Zephyr RTOS shall provide an interface for managing a defined set of hardware exceptions (including interrupts) across all systems.
- STATUS: Draft
- TYPE: Functional
- COMPONENT: Device Driver API
- USER_STORY: As a Zephyr RTOS user I want hardware exceptions (hardware failures, programming mistakes) to be handled gracefully (no program crashes as far as possible).

# Specification: Exception and Error Handling

## R28 (TEXT)
SPDX-License-Identifier: Apache-2.0

## ZEP-SRS-16-1: Fatal Exception Error Handler (REQUIREMENT)
The Zephyr RTOS shall provide default handlers for exceptions.
- STATUS: Draft
- TYPE: Functional
- COMPONENT: Exception and Error Handling
- USER_STORY: As a Zephyr RTOS user I want exceptions which I did not handle explicitly (by mistake or on purpose) to be caught by a default handler, defined either by Zephyr OS or by myself.

## ZEP-SRS-16-2: Default handler for fatal errors (REQUIREMENT)
The Zephyr RTOS shall provide default handlers for fatal errors that do not have a dedicated handler.
- STATUS: Draft
- TYPE: Functional
- COMPONENT: Exception and Error Handling

## ZEP-SRS-16-3: Assigning a specific handler (REQUIREMENT)
The Zephyr RTOS shall provide an interface to assign a specific handler with an exception.
- STATUS: Draft
- TYPE: Functional
- COMPONENT: Exception and Error Handling

## ZEP-SRS-16-4: Assigning a specific handler (2) (REQUIREMENT)
The Zephyr RTOS shall provide an interface to assign a specific handler for a fatal error.
- STATUS: Draft
- TYPE: Functional
- COMPONENT: Exception and Error Handling

# Specification: Tracing

## ZEP-SRS-24-1: FIFO definition at compile time (REQUIREMENT)
The Zephyr RTOS shall provide a mechanism to define and initialize a FIFO at compile time.
- STATUS: Draft
- TYPE: Functional
- COMPONENT: FIFOs
- Parent -> ZEP-SYRS-24

## ZEP-SRS-24-2: FIFO cancel waiting thread (REQUIREMENT)
The Zephyr RTOS shall provide a mechanism for the first thread waiting to get and dequeue a data item to return as if the timeout had expired.
- STATUS: Draft
- TYPE: Functional
- COMPONENT: FIFOs
- Parent -> ZEP-SYRS-24

## ZEP-SRS-24-3: FIFO enqueue item to the back (REQUIREMENT)
The Zephyr RTOS shall provide a mechanism to enqueue a data item to the back of a FIFO (i.e. append).
- STATUS: Draft
- TYPE: Functional
- COMPONENT: FIFOs
- Parent -> ZEP-SYRS-24

## ZEP-SRS-24-4: FIFO implicit memory allocation (REQUIREMENT)
The Zephyr RTOS shall provide a mechanism to allocate memory from a thread when enqueuing data items to a FIFO.
- STATUS: Draft
- TYPE: Functional
- COMPONENT: FIFOs
- Parent -> ZEP-SYRS-24

## ZEP-SRS-24-5: FIFO append item list to the back (REQUIREMENT)
The Zephyr RTOS shall provide a mechanism to append a list of data items to the back of a FIFO.
- STATUS: Draft
- TYPE: Functional
- COMPONENT: FIFOs
- Parent -> ZEP-SYRS-24

## ZEP-SRS-24-6: FIFO append and empty item list to the back (REQUIREMENT)
The Zephyr RTOS shall provide a mechanism to append a list of data items to the back of a FIFO and then empty the list.
- STATUS: Draft
- TYPE: Functional
- COMPONENT: FIFOs
- Parent -> ZEP-SYRS-24

## ZEP-SRS-24-7: FIFO get and dequeue item from front (REQUIREMENT)
The Zephyr RTOS shall provide a mechanism to get and dequeue a data item from the front of a FIFO, within a timeout.
- STATUS: Draft
- TYPE: Functional
- COMPONENT: FIFOs
- Parent -> ZEP-SYRS-24

## ZEP-SRS-24-8: FIFO empty check (REQUIREMENT)
The Zephyr RTOS shall provide a mechanism to check if a FIFO is empty.
- STATUS: Draft
- TYPE: Functional
- COMPONENT: FIFOs
- Parent -> ZEP-SYRS-24

## ZEP-SRS-24-9: FIFO peek item at front (REQUIREMENT)
The Zephyr RTOS shall provide a mechanism to peek at the data data item at the front of a FIFO.
- STATUS: Draft
- TYPE: Functional
- COMPONENT: FIFOs
- Parent -> ZEP-SYRS-24

## ZEP-SRS-24-10: FIFO peek item at back (REQUIREMENT)
The Zephyr RTOS shall provide a mechanism to peek at the data item at the back of a FIFO.
- STATUS: Draft
- TYPE: Functional
- COMPONENT: FIFOs
- Parent -> ZEP-SYRS-24

## ZEP-SRS-24-11: Queue definition at compile time (REQUIREMENT)
The Zephyr RTOS shall provide a mechanism to define and initialize a FIFO at compile time.
- STATUS: Draft
- TYPE: Functional
- COMPONENT: Queues
- Parent -> ZEP-SYRS-21

# Specification: File system

## R44 (TEXT)
SPDX-License-Identifier: Apache-2.0

## ZEP-SRS-17-1: Create file (REQUIREMENT)
Zephyr shall provide file create capabilities for files on the file system.
- STATUS: Draft
- TYPE: Functional
- COMPONENT: File System
- USER_STORY: As a Zephyr OS user I want to be able to create a new file or overwrite an existing file at the same filesystem location / identifier (e.g. path + name).

## ZEP-SRS-17-2: Open files (REQUIREMENT)
Zephyr shall provide file open capabilities for files on the file system.
- STATUS: Draft
- TYPE: Functional
- COMPONENT: File System
- USER_STORY: As a Zephyr OS user I want to be able to open a file for writing or reading.
  When opened for writing, I want to have exclusive access to the file.

## ZEP-SRS-17-3: Read files (REQUIREMENT)
Zephyr shall provide read access to files in the file system.
- STATUS: Draft
- TYPE: Functional
- COMPONENT: File System
- USER_STORY: As a Zephyr OS user I want to be able to read from an existing file, also while the file is read from multiple and write accessed from one other instances.

## ZEP-SRS-17-4: Write to files (REQUIREMENT)
Zephyr shall provide write access to the files in the file system.
- STATUS: Draft
- TYPE: Functional
- COMPONENT: File System
- USER_STORY: As a Zephyr OS user I want to be able to write to a file either from the beginning of the file or appending at the end.

## ZEP-SRS-17-5: Close file (REQUIREMENT)
Zephyr shall provide file close capabilities for files on the file system.
- STATUS: Draft
- TYPE: Functional
- COMPONENT: File System
- USER_STORY: As a Zephyr OS user I want to be able to close a file after being finished with my file operations, unlocking any access restrictions.

## ZEP-SRS-17-6: Move file (REQUIREMENT)
Zephyr shall provide the capability to move files on the file system.
- STATUS: Draft
- TYPE: Functional
- COMPONENT: File System

## ZEP-SRS-17-7: Delete file (REQUIREMENT)
Zephyr shall provide file delete capabilities for files on the file system.
- STATUS: Draft
- TYPE: Functional
- COMPONENT: File System
- USER_STORY: As a Zephyr OS user I want to be able to delete an existing file.

# Specification: Hardware Architecture Interface

## R52 (TEXT)
SPDX-License-Identifier: Apache-2.0

## ZEP-SRS-19-1: Atomic Operations (REQUIREMENT)
The Zephyr RTOS shall provide an interface functionality to access memory while ensuring mutual exclusion. Note: Implementation by atomic variables and accessing them by APIs.
- STATUS: Draft
- TYPE: Functional
- COMPONENT: Hardware Architecture Interface
- USER_STORY: As a Zephyr RTOS user I want to read from or write into a memory areas without being disturbed by other threads or ISRs.
- Parent -> ZEP-SYRS-1

## ZEP-SRS-19-2: Thread Context Switching (REQUIREMENT)
The Zephyr RTOS shall provide a mechanism for context switching between threads.
- STATUS: Draft
- TYPE: Functional
- COMPONENT: Hardware Architecture Interface
- USER_STORY: As a Zephyr RTOS user I want to execute code concurrently in one or more threads and when interrupted at a code location in a thread, to continue at the very same location.
- Parent -> ZEP-SYRS-1

## ZEP-SRS-19-3: Software Exceptions (REQUIREMENT)
The Zephyr RTOS shall provide an interface to implement software exceptions.
- STATUS: Draft
- TYPE: Functional
- COMPONENT: Hardware Architecture Interface
- USER_STORY: As a Zephyr RTOS user I want to catch any software exception and handle it according to my application needs.
- Parent -> ZEP-SYRS-1

## ZEP-SRS-19-4: Processor Mode Support (REQUIREMENT)
The Zephyr RTOS shall provide an interface for managing processor modes.
- STATUS: Draft
- TYPE: Functional
- COMPONENT: Hardware Architecture Interface
- USER_STORY: If MCU power state was meant here:
  As a Zephyr RTOS user I want to control the MCU's power saving mode such e.g. operation, sleep, deep sleep or similar as supported by the selected MCU.
- Parent -> ZEP-SYRS-1

# Specification: Zephyr Software Requirements

## R57 (TEXT)
SPDX-License-Identifier: Apache-2.0

# Specification: Interrupts

## R58 (TEXT)
SPDX-License-Identifier: Apache-2.0

## ZEP-SRS-7-1: Installing static IRQ service routines (ISR). (REQUIREMENT)
Zephyr RTOS shall provide a mechanism to initialize a static IRQ service routine (ISR),
providing all parameters needed to configure the hardware and software.
- STATUS: Draft
- TYPE: Functional
- COMPONENT: Interrupts
- Parent -> ZEP-SYRS-7

## ZEP-SRS-7-2: Static IRQ initial status. (REQUIREMENT)
The static IRQ shall be initially disabled.
- STATUS: Draft
- TYPE: Functional
- COMPONENT: Interrupts
- Parent -> ZEP-SYRS-7

## ZEP-SRS-7-3: Installing direct IRQ service routines (ISR). (REQUIREMENT)
Zephyr RTOS shall provide a mechanism to initialize a direct IRQ handler,
providing all parameters needed to configure the hardware and software.
- STATUS: Draft
- TYPE: Functional
- COMPONENT: Interrupts
- USER_STORY: As the developer of low-power and low-latency applications, I need to implement ISRs 
  that avoid the normal interrupt and power management overhead.
- Parent -> ZEP-SYRS-7

## ZEP-SRS-7-4: Direct IRQ initial status. (REQUIREMENT)
The direct IRQ shall be initially disabled.
- STATUS: Draft
- TYPE: Functional
- COMPONENT: Interrupts
- Parent -> ZEP-SYRS-7

## ZEP-SRS-7-5: Installing dynamic IRQ service routines (ISR). (REQUIREMENT)
Zephyr RTOS shall provide a mechanism to initialize a dynamic IRQ service routine, 
providing all parameters needed to configure the hardware and software.
- STATUS: Draft
- TYPE: Functional
- COMPONENT: Interrupts
- Parent -> ZEP-SYRS-7

## ZEP-SRS-7-6: Dynamic IRQ initial status. (REQUIREMENT)
The dynamic IRQ shall be initially disabled.
- STATUS: Draft
- TYPE: Functional
- COMPONENT: Interrupts
- Parent -> ZEP-SYRS-7

## ZEP-SRS-7-7: Uninstalling dynamic IRQ service routines (ISR). (REQUIREMENT)
Zephyr RTOS shall provide a mechanism to uninstall a dynamic ISR.
- STATUS: Draft
- TYPE: Functional
- COMPONENT: Interrupts
- Parent -> ZEP-SYRS-7

## ZEP-SRS-7-8: Global IRQ disable (REQUIREMENT)
Zephyr RTOS shall provide a mechanism to Disable all IRQs on a CPU, and 
return the state the IRQ hardware prior to being disabled.
- STATUS: Draft
- TYPE: Functional
- COMPONENT: Interrupts
- Parent -> ZEP-SYRS-7

## ZEP-SRS-7-9: Global IRQ enable (REQUIREMENT)
Zephyr RTOS shall provide a mechanism to Enable all IRQs on a CPU 
and return them to thier previous state.
- STATUS: Draft
- TYPE: Functional
- COMPONENT: Interrupts
- Parent -> ZEP-SYRS-7

## ZEP-SRS-7-10: Specific IRQ disable (REQUIREMENT)
Zephyr RTOS shall provide a mechanism to Disable a specified IRQ.
- STATUS: Draft
- TYPE: Functional
- COMPONENT: Interrupts
- Parent -> ZEP-SYRS-7

## ZEP-SRS-7-11: Specific IRQ enable (REQUIREMENT)
Zephyr RTOS shall provide a mechanism to Enable a specified IRQ.
- STATUS: Draft
- TYPE: Functional
- COMPONENT: Interrupts
- Parent -> ZEP-SYRS-7

## ZEP-SRS-7-12: IRQ Enabled status (REQUIREMENT)
Zephyr RTOS shall provide mechanisms that returns the Enabled status 
of a specified IRQ, where the status is Enabled or Disabled.
- STATUS: Draft
- TYPE: Functional
- COMPONENT: Interrupts
- Parent -> ZEP-SYRS-7

## ZEP-SRS-7-13: ISR Context status (REQUIREMENT)
Zephyr RTOS shall provide mechanisms that returns the execution context, 
where the context is In-ISR or Not In-ISR.
- STATUS: Draft
- TYPE: Functional
- COMPONENT: Interrupts
- USER_STORY: As the developer of functions that may run in either ISR or THREAD context, 
  I need to know the current context to enable condition behavior.
- Parent -> ZEP-SYRS-7

## ZEP-SRS-7-14: Multi-level interrupts (REQUIREMENT)
The Zephyr RTOS shall support multi-level preemptive interrupt priorities, when supported by hardware.
- STATUS: Draft
- TYPE: Functional
- COMPONENT: Interrupts
- Parent -> ZEP-SYRS-7

# Specification: Tracing

## ZEP-SRS-23-1: LIFO definition at compile time (REQUIREMENT)
The Zephyr RTOS shall provide a mechanism to define and initialize a LIFO at compile time.
- STATUS: Draft
- TYPE: Functional
- COMPONENT: LIFOs
- Parent -> ZEP-SYRS-23

## ZEP-SRS-23-2: LIFO enqueue item to the back (REQUIREMENT)
The Zephyr RTOS shall provide a mechanism to enqueue a data item to the back of a LIFO (i.e. prepend).
- STATUS: Draft
- TYPE: Functional
- COMPONENT: LIFOs
- Parent -> ZEP-SYRS-23

## ZEP-SRS-23-3: LIFO implicit memory allocation (REQUIREMENT)
The Zephyr RTOS shall provide a mechanism to allocate memory from a thread when enqueuing data items to a LIFO.
- STATUS: Draft
- TYPE: Functional
- COMPONENT: LIFOs
- Parent -> ZEP-SYRS-23

## ZEP-SRS-23-4: LIFO get and dequeue item from front (REQUIREMENT)
The Zephyr RTOS shall provide a mechanism to get and dequeue a data item from the back of a LIFO, within a timeout.
- STATUS: Draft
- TYPE: Functional
- COMPONENT: LIFOs
- Parent -> ZEP-SYRS-23

## ZEP-SRS-23-5: Queue definition at compile time (REQUIREMENT)
The Zephyr RTOS shall provide a mechanism to define and initialize a LIFO at compile time.
- STATUS: Draft
- TYPE: Functional
- COMPONENT: Queues
- Parent -> ZEP-SYRS-23

# Specification: Logging

## R78 (TEXT)
SPDX-License-Identifier: Apache-2.0

## ZEP-SRS-11-1: Dedicated Logging Thread Support (REQUIREMENT)
The Zephyr RTOS shall support isolation of logging from other functionality.
- STATUS: Draft
- TYPE: Functional
- COMPONENT: Logging
- USER_STORY: As a Zephyr RTOS user I want to be able to configure logging of events so the execution of logging activities does have no or only a minimal impact to the timing behaviour of my application.

## ZEP-SRS-11-2: Logs available for post processing (REQUIREMENT)
The Zephyr RTOS logging shall produce logs that are capable of being post processed.
- STATUS: Draft
- TYPE: Functional
- COMPONENT: Logging
- USER_STORY: As a Zephyr RTOS user I want the logging information to be stored in a format which allows to be read possibly converted or displayed by COTS tools.

## ZEP-SRS-11-3: Formatting log messages (REQUIREMENT)
The Zephyr RTOS logging shall support formatting of log messages to enable filtering.
- STATUS: Draft
- TYPE: Functional
- COMPONENT: Logging
- USER_STORY: As a Zephyr RTOS user I want to be able my application to format texts (printf alike) into the log message.

## ZEP-SRS-11-4: Logging Filtering Support (REQUIREMENT)
The Zephyr RTOS logging system shall support filtering based on severity level.
- STATUS: Draft
- TYPE: Functional
- COMPONENT: Logging
- USER_STORY: As a Zephyr RTOS user I want to be able to distinguish between different severity level for my log messages (e.g. DEBUG, INFO, WARN, ERROR, PANIC).

## ZEP-SRS-11-5: Multiple Backend Logging Support (REQUIREMENT)
The Zephyr RTOS shall support logging messages to multiple system resources.
- STATUS: Draft
- TYPE: Functional
- COMPONENT: Logging
- USER_STORY: As a Zephyr RTOS user I want to be able to simultaneously log to different channels which may store / redirect the information on / to different hardware (EEPROM, Flash, FRAM, UART, Ethernet, USB etc.).

## ZEP-SRS-11-6: Deferred Logging Support (REQUIREMENT)
The Zephyr RTOS shall support deferred logging (TODO: need more detail about the constraints and limits on what can be deferred).
- STATUS: Draft
- TYPE: Functional
- COMPONENT: Logging
- USER_STORY: As a Zephyr RTOS user I want a minimal influence of logging activities to the timing behaviour of my application. Time consuming logging threads shall be done in the background.

# Specification: Mailboxes

## R85 (TEXT)
SPDX-License-Identifier: Apache-2.0

## ZEP-SRS-25-1: Mailbox Initialization At Run Time (REQUIREMENT)
The Zephyr RTOS shall provide a mechanism to define and initialize a mailbox at run time.
- STATUS: Draft
- TYPE: Functional
- COMPONENT: Mailboxes
- USER_STORY: As a Zephyr RTOS developer, I want to be able to initialize a mailbox instance so that it is ready to be used for message exchange between threads.
- Parent -> ZEP-SYRS-25

## ZEP-SRS-25-2: Mailbox Initialization At Compile Time (REQUIREMENT)
The Zephyr RTOS shall provide a mechanism to statically define and initialize a mailbox object at compile time.
- STATUS: Draft
- TYPE: Functional
- COMPONENT: Mailboxes
- USER_STORY: As a Zephyr RTOS developer, I want to be able to statically define and initialize a mailbox at compile time so that it is available immediately without runtime initialization.
- Parent -> ZEP-SYRS-25

## ZEP-SRS-25-3: Message Size Support (REQUIREMENT)
The Zephyr RTOS shall support messages containing zero or more bytes of data.
- STATUS: Draft
- TYPE: Functional
- COMPONENT: Mailboxes
- USER_STORY: As a Zephyr RTOS developer, I want to be able to send messages of different sizes using the same mailbox so that I can efficiently communicate different types of information between threads.
- Parent -> ZEP-SYRS-25

## ZEP-SRS-25-4: Mailbox Data Transfer (REQUIREMENT)
The Zephyr RTOS shall handle the data transfer between mailbox objects of the sending and receiving threads.
- STATUS: Draft
- TYPE: Functional
- COMPONENT: Mailboxes
- Parent -> ZEP-SYRS-25

## ZEP-SRS-25-5: Synchronous Message Sending (REQUIREMENT)
The Zephyr RTOS shall provide a mechanism for a thread to send a message through a mailbox and block until the message is processed or a timeout occurs.
- STATUS: Draft
- TYPE: Functional
- COMPONENT: Mailboxes
- USER_STORY: As a Zephyr RTOS developer, I want to be able to send a message and wait for it to be processed so that I can be sure the message was received before continuing execution.
- Parent -> ZEP-SYRS-25

## ZEP-SRS-25-6: Synchronous Send Timeout Handling (REQUIREMENT)
If the synchronous message send operation times out before a receiver processes the message, the Zephyr RTOS shall return an timeout error code to the sending thread.
- STATUS: Draft
- TYPE: Functional
- COMPONENT: Mailboxes
- USER_STORY: As a Zephyr RTOS developer, I want to be able to limit how long my thread waits for a message to be received so that I can implement fallback behavior if communication takes too long.
- Parent -> ZEP-SYRS-25

## ZEP-SRS-25-7: Asynchronous Message Sending (REQUIREMENT)
The Zephyr RTOS shall provide a mechanism for a thread to send a message through a mailbox without waiting for it to be processed.
- STATUS: Draft
- TYPE: Functional
- COMPONENT: Mailboxes
- USER_STORY: As a Zephyr RTOS developer, I want to be able to send a message without waiting for it to be processed so that my thread can continue execution immediately.
- Parent -> ZEP-SYRS-25

## ZEP-SRS-25-8: Asynchronous Completion Signaling (REQUIREMENT)
When a sending thread asynchronously sends a message to a mailbox object, the Zephyr RTOS shall provide a mechanism to signal to the sending thread that the message has been both received and completely processed by the receiver.
- STATUS: Draft
- TYPE: Functional
- COMPONENT: Mailboxes
- USER_STORY: As a Zephyr RTOS developer, I want to be notified when my asynchronously sent message has been fully processed so that I can perform follow-up actions without polling.
- Parent -> ZEP-SYRS-25

## ZEP-SRS-25-9: Message Reception (REQUIREMENT)
The Zephyr RTOS shall provide a mechanism for a thread to receive a message via a mailbox object with a timeout parameter.
- STATUS: Draft
- TYPE: Functional
- COMPONENT: Mailboxes
- USER_STORY: As a Zephyr RTOS developer, I want to be able to receive messages from other threads with control over how long to wait for a message to arrive.
- Parent -> ZEP-SYRS-25

## ZEP-SRS-25-10: Message Data Retrieval (REQUIREMENT)
The Zephyr RTOS shall provide a mechanism for a thread to retrieve message data via a mailbox object.
- STATUS: Draft
- TYPE: Functional
- COMPONENT: Mailboxes
- USER_STORY: As a Zephyr RTOS developer, I want to be able to extract message data into my buffer after message reception so that I can process the information contained in the message.
- Parent -> ZEP-SYRS-25

## ZEP-SRS-25-11: Message Reception Blocking (REQUIREMENT)
When a receiving thread requests a message via a mailbox object and no message is available, the Zephyr RTOS shall block the receiving thread until a message is available or the timeout expires.
- STATUS: Draft
- TYPE: Functional
- COMPONENT: Mailboxes
- Parent -> ZEP-SYRS-25

## ZEP-SRS-25-12: Message Reception Timeout Handling (REQUIREMENT)
If the message receive operation times out before a message becomes available, the Zephyr RTOS shall return an appropriate timeout error code to the receiving thread.
- STATUS: Draft
- TYPE: Functional
- COMPONENT: Mailboxes
- USER_STORY: As a Zephyr RTOS developer, I want to be able to limit how long my thread waits for a message to arrive so that I can implement fallback behavior if communication takes too long.
- Parent -> ZEP-SYRS-25

## ZEP-SRS-25-13: Non-Anonymous Messaging (REQUIREMENT)
The Zephyr RTOS shall handle message exchange via a mailbox object non-anonymously, allowing both the sending and receiving threads to know the identity of the other thread.
- STATUS: Draft
- TYPE: Functional
- COMPONENT: Mailboxes
- USER_STORY: As a Zephyr RTOS developer, I want to be able to identify the source or destination of messages so that I can implement thread-specific handling of message content.
- Parent -> ZEP-SYRS-25

## ZEP-SRS-25-14: Priority-Based Message Delivery (REQUIREMENT)
When multiple threads are waiting on an empty mailbox object, the Zephyr RTOS shall deliver the next message to the highest priority thread.
- STATUS: Draft
- TYPE: Functional
- COMPONENT: Mailboxes
- USER_STORY: As a Zephyr RTOS developer, I want message delivery to respect thread priorities so that higher priority tasks receive messages before lower priority ones.
- Parent -> ZEP-SYRS-25

## ZEP-SRS-25-15: Priority-Based Message Delivery (REQUIREMENT)
When multiple threads of equal priority are waiting on an empty mailbox object, the Zephyr RTOS shall deliver the next message to the thread that has waited the longest.
- STATUS: Draft
- TYPE: Functional
- COMPONENT: Mailboxes
- Parent -> ZEP-SYRS-25

## ZEP-SRS-25-16: Mailbox Quantity Support (REQUIREMENT)
The Zephyr RTOS shall support an arbitrary number of mailbox objects, limited only by available RAM in the system.
- STATUS: Draft
- TYPE: Functional
- COMPONENT: Mailboxes
- USER_STORY: As a Zephyr RTOS developer, I want to be able to create as many mailboxes as my application needs without arbitrary limitations so that I can design my communication architecture freely.
- Parent -> ZEP-SYRS-25

## ZEP-SRS-25-17: Invalid Parameter Handling (REQUIREMENT)
The Zephyr RTOS shall handle invalid parameters by returning error codes rather than causing system failures.
- STATUS: Draft
- TYPE: Functional
- COMPONENT: Mailboxes
- USER_STORY: As a Zephyr RTOS developer, I want the system to validate my inputs and return errors rather than crash when I provide invalid parameters so that I can develop more robust applications.
- Parent -> ZEP-SYRS-25

# Specification: Memory Objects

## R103 (TEXT)
SPDX-License-Identifier: Apache-2.0

## ZEP-SRS-9-1: Dynamic Memory Allocation (REQUIREMENT)
The Zephyr RTOS shall allow threads to dynamically allocate variable-sized memory regions from a specified range of memory.
- STATUS: Draft
- TYPE: Functional
- COMPONENT: Memory Objects
- USER_STORY: As a Zephyr RTOS user I want my application to be able to dynamically allocate memory of a application defined size.

## ZEP-SRS-9-2: Memory Slab Object (REQUIREMENT)
The Zephyr RTOS shall allow threads to dynamically allocate fixed-sized memory regions from a specified range of memory.
- STATUS: Draft
- TYPE: Functional
- COMPONENT: Memory Objects
- USER_STORY: As a Zephyr RTOS user I want a most efficient and least fragmentation prone dynamic memory allocation mechanism.

# Specification: Memory protection

## R106 (TEXT)
SPDX-License-Identifier: Apache-2.0

## ZEP-SRS-8-1: Memory Protection (REQUIREMENT)
The Zephyr RTOS shall support memory protection features to isolate a thread's memory region.
- STATUS: Draft
- TYPE: Functional
- USER_STORY: As a Zephyr RTOS user I want memory to be allocated and protected to my application threads preventing mistakenly access to foreign memory as far as the hardware allows.

## ZEP-SRS-8-2: Granting access to kernel objects (REQUIREMENT)
The Zephyr RTOS shall provide a mechanism to grant user threads access to kernel objects.
- STATUS: Draft
- TYPE: Functional
- COMPONENT: Memory Protection
- USER_STORY: As a Zephyr RTOS user I want, from the user space, under certain conditions, access to kernel objects.

## ZEP-SRS-8-3: Separation between user and kernel threads for memory access (REQUIREMENT)
The Zephyr RTOS shall be able to differentiate between user threads and kernel threads for memory access.
- STATUS: Draft
- TYPE: Functional
- COMPONENT: Memory Protection
- USER_STORY: As a Zephyr RTOS user I want, from the kernel space, unconditioned access to kernel objects.

## ZEP-SRS-8-4: Safely handle unimplemented calls or invalid system calls (REQUIREMENT)
The Zephyr RTOS shall have a defined behaviour when an invocation of an unimplemented system call is made.
- STATUS: Draft
- TYPE: Functional
- COMPONENT: Memory Protection
- USER_STORY: As a Zephyr RTOS user I want Zephyr OS to indicate any unimplemented system call by an appropriate error message.

## ZEP-SRS-8-5: Response to invalid system call IDs (REQUIREMENT)
The Zephyr RTOS shall have a defined behaviour when an invalid system call ID is used.
- STATUS: Draft
- TYPE: Functional
- COMPONENT: Memory Protection
- USER_STORY: As a Zephyr RTOS user I want Zephyr OS to indicate invalid system call by an appropriate error message.

## ZEP-SRS-8-6: Prevent user threads creating higher priority threads (REQUIREMENT)
The Zephyr RTOS shall prevent user threads from creating new threads that are higher priority than the caller.
- STATUS: Draft
- TYPE: Functional
- COMPONENT: Memory Protection

## ZEP-SRS-8-7: Revoking threads permissions on a kernel object (REQUIREMENT)
The Zephyr RTOS shall support revoking permission to a kernel object. User mode threads may only revoke their own access to an object.
- STATUS: Draft
- TYPE: Functional
- COMPONENT: Memory Protection
- USER_STORY: As a Zephyr RTOS user I want to be protected against other user threads changing access to kernel objects of my thread.

## ZEP-SRS-8-8: Prevent user threads creating supervisor threads (REQUIREMENT)
The Zephyr RTOS shall prevent user threads from creating kernel threads.
- STATUS: Draft
- TYPE: Functional
- COMPONENT: Memory Protection
- USER_STORY: As a Zephyr RTOS user I want to be protected against user threads creating higher privileged kernel/supervisor threads.

## ZEP-SRS-8-9: Reduced Privilege Level Threads (REQUIREMENT)
The Zephyr RTOS shall allow the creation of threads that run in reduced privilege level.
- STATUS: Draft
- TYPE: Functional
- COMPONENT: Memory Protection
- USER_STORY: As a Zephyr RTOS user I want to be able to create lower privileged threads than my own.

## ZEP-SRS-8-10: User Mode Threads Performing Privileged Operations (REQUIREMENT)
The Zephyr RTOS shall provide system calls to allow user mode threads to perform privileged operations.
- STATUS: Draft
- TYPE: Functional
- COMPONENT: Memory Protection
- USER_STORY: As a Zephyr RTOS user I want to be able to perform privileged operations in the kernel mode through a well defined interface.

## ZEP-SRS-8-11: User mode handling of detected stack overflow (REQUIREMENT)
The Zephyr RTOS shall support a defined mechanism for user mode handling a of detected stack overflow.
- STATUS: Draft
- TYPE: Functional
- COMPONENT: Memory Protection
- USER_STORY: As a Zephyr RTOS user I want, when a stack overflow is detected, to be able to implement a graceful, application defined handling of the exception.

## ZEP-SRS-8-12: Stack Overflow Detection (REQUIREMENT)
The Zephyr RTOS shall support detection of stack overflows.
- STATUS: Draft
- TYPE: Functional
- COMPONENT: Memory Protection
- USER_STORY: As a Zephyr RTOS user I want to get an indication when a stack overflow occurs at least during debugging / the development phase, and for safety applications also in a release version of my application.

## ZEP-SRS-8-13: Boot Time Memory Access Policy (REQUIREMENT)
The Zephyr RTOS shall support configurable access to memory during boot time.
- STATUS: Draft
- TYPE: Functional
- COMPONENT: Memory Protection

## ZEP-SRS-8-14: System Call Handler Functions (REQUIREMENT)
The Zephyr RTOS shall provide helper functions for system call handler functions to validate the inputs passed in from user mode before invoking the implementation function to protect the kernel.
- STATUS: Draft
- TYPE: Functional
- COMPONENT: Memory Protection
- USER_STORY: As a Zephyr RTOS user I want Zepyhr OS to validate system call parameters passed from the user mode to the kernel mode to avoid crashes and undefined behaviour.

## ZEP-SRS-8-15: System Call C strings in user mode (REQUIREMENT)
The Zephyr RTOS shall support system calls to be able to safely accept C strings passed in from user mode.
- STATUS: Draft
- TYPE: Functional
- COMPONENT: Memory Protection
- USER_STORY: As a Zephyr RTOS user I want Zepyhr OS to validate system call string type parameters passed from the user mode to the kernel mode to avoid crashes and undefined behaviour.

  e.g.

  - verify the string length is smaller or equal to the syscalls defined max.
  - verify that the length type does not overflow when allocating one more byte ???

## ZEP-SRS-8-16: Tracking kernel objects in used by user mode threads (REQUIREMENT)
The Zephyr RTOS shall track kernel objects that are used by user mode threads.

Note: this means Zephyr shall track the resources used by the user mode thread (associate this with a user story).
- STATUS: Draft
- TYPE: Functional
- COMPONENT: Memory Protection

## ZEP-SRS-8-17: Granting threads access to specific memory (REQUIREMENT)
The Zephyr RTOS shall have an interface to request access to specific memory after initial allocation.
- STATUS: Draft
- TYPE: Functional
- COMPONENT: Memory Protection
- USER_STORY: As a Zephyr RTOS user I want to be able to request read-only or read-write access to a dedicated memory area/pool during runtime.

## ZEP-SRS-8-18: Assigning memory pools to act as a thread resource pool (REQUIREMENT)
The Zephyr RTOS shall support assigning a memory pool to act as that thread's resource pool.
- STATUS: Draft
- TYPE: Functional
- COMPONENT: Memory Protection
- USER_STORY: As a Zephyr RTOS user I want to be able, during runtime from the kernel, to request a memory area/pool which is exclusively available to the requesting thread protected against access from other threads.

# Specification: Mutex

## R125 (TEXT)
SPDX-License-Identifier: Apache-2.0

## ZEP-SRS-6-1: Mutex Kernel Object (REQUIREMENT)
The Zephyr RTOS shall support resource synchronization. (Note synchronization can be for memory access, and mutex may be one implementation, but not the only one).
- STATUS: Draft
- TYPE: Functional
- COMPONENT: Mutex
- USER_STORY: As a Zephyr RTOS user I want to be able to sychonize threads when accessing common resources, where the thread shall have the option to:
  - wait eternally until the resources becomes available.
  - immediately return with a negative message if the resource is not available and allow the thread to continue.
  - wait for a given time for the resource to become available or return with a negative message.

# Specification: Power Management

## R127 (TEXT)
SPDX-License-Identifier: Apache-2.0

## ZEP-SRS-13-1: Power State Control (REQUIREMENT)
The Zephyr RTOS shall provide control over changes to system power states.
- STATUS: Draft
- TYPE: Functional
- COMPONENT: Power Management
- USER_STORY: See ZEP104
  +
  When the power state is changed I want to get an notification in order for specific parts of my application to react accordingly.

## ZEP-SRS-13-2: Power Management (REQUIREMENT)
TBD
- STATUS: Draft
- TYPE: Functional

## ZEP-SRS-13-3: Notification of changes to system power states (REQUIREMENT)
The Zephyr RTOS shall provide notification of changes to system power states.
- STATUS: Draft
- TYPE: Functional
- COMPONENT: Power Management

# Specification: Tracing

## ZEP-SRS-20-1: Queue definition at compile time (REQUIREMENT)
The Zephyr RTOS shall provide a mechanism to define and initialize a queue at compile time.
- STATUS: Draft
- TYPE: Functional
- COMPONENT: Queues
- Parent -> ZEP-SYRS-21

## ZEP-SRS-20-2: Queue definition at run time. (REQUIREMENT)
The Zephyr RTOS shall provide a mechanism to define and initialize a queue at run time.
- STATUS: Draft
- TYPE: Functional
- COMPONENT: Queues
- Parent -> ZEP-SYRS-21

## ZEP-SRS-20-3: Queue enqueue item to the back (REQUIREMENT)
The Zephyr RTOS shall provide a mechanism to enqueue a data item to the back of a queue (i.e. append).
- STATUS: Draft
- TYPE: Functional
- COMPONENT: Queues
- Parent -> ZEP-SYRS-21

## ZEP-SRS-20-4: Queue enqueue item to the front (REQUIREMENT)
The Zephyr RTOS shall provide a mechanism to enqueue a data item to the front of a queue (i.e. prepend).
- STATUS: Draft
- TYPE: Functional
- COMPONENT: Queues
- Parent -> ZEP-SYRS-21

## ZEP-SRS-20-5: Queue remove item (REQUIREMENT)
The Zephyr RTOS shall provide a mechanism to remove a specific data item from a queue.
- STATUS: Draft
- TYPE: Functional
- COMPONENT: Queues
- Parent -> ZEP-SYRS-21

## ZEP-SRS-20-6: Queue get and dequeue item from front (REQUIREMENT)
The Zephyr RTOS shall provide a mechanism to get and dequeue a data item from the front of a queue, within a timeout.
- STATUS: Draft
- TYPE: Functional
- COMPONENT: Queues
- Parent -> ZEP-SYRS-21

## ZEP-SRS-20-7: Queue empty check (REQUIREMENT)
The Zephyr RTOS shall provide a mechanism to check if a queue is empty.
- STATUS: Draft
- TYPE: Functional
- COMPONENT: Queues
- Parent -> ZEP-SYRS-21

## ZEP-SRS-20-8: Queue peek item at back (REQUIREMENT)
The Zephyr RTOS shall provide a mechanism to peek at the data data item at the back of a queue.
- STATUS: Draft
- TYPE: Functional
- COMPONENT: Queues
- Parent -> ZEP-SYRS-21

## ZEP-SRS-20-9: Queue peek item at front (REQUIREMENT)
The Zephyr RTOS shall provide a mechanism to peek at the data data item at the front of a queue.
- STATUS: Draft
- TYPE: Functional
- COMPONENT: Queues
- Parent -> ZEP-SYRS-21

## ZEP-SRS-20-10: Queue insert (REQUIREMENT)
The Zephyr RTOS shall provide a mechanism to insert a data item behind another specific data item in a queue.
- STATUS: Draft
- TYPE: Functional
- COMPONENT: Queues
- Parent -> ZEP-SYRS-21

## ZEP-SRS-20-11: Queue append item list to the back (REQUIREMENT)
The Zephyr RTOS shall provide a mechanism to append a list of data items to the back of a queue.
- STATUS: Draft
- TYPE: Functional
- COMPONENT: Queues
- Parent -> ZEP-SYRS-21

## ZEP-SRS-20-12: Queue append and empty item list to the back (REQUIREMENT)
The Zephyr RTOS shall provide a mechanism to append a list of data items to the back of a queue and then empty the list.
- STATUS: Draft
- TYPE: Functional
- COMPONENT: Queues
- Parent -> ZEP-SYRS-21

## ZEP-SRS-20-13: Queue append unique data item (REQUIREMENT)
The Zephyr RTOS shall provide a mechanism to append a data item uniquely to the queue.
- STATUS: Draft
- TYPE: Functional
- COMPONENT: Queues
- Parent -> ZEP-SYRS-21

## ZEP-SRS-20-14: Queue implicit memory allocation (REQUIREMENT)
The Zephyr RTOS shall provide a dedicated mechanism to implicite allocate memory from a thread when appending
data items to a queue.
- STATUS: Draft
- TYPE: Functional
- COMPONENT: Queues
- Parent -> ZEP-SYRS-21

# Specification: Semaphores

## R145 (TEXT)
SPDX-License-Identifier: Apache-2.0

## ZEP-SRS-5-1: Counting Semaphore Definition At Compile Time (REQUIREMENT)
The Zephyr RTOS shall provide a mechanism to define and initialize a semaphore at compile time.
- STATUS: Draft
- TYPE: Functional
- COMPONENT: Semaphore
- Parent -> ZEP-SYRS-14

## ZEP-SRS-5-2: Counting Semaphore Definition At Run Time (REQUIREMENT)
The Zephyr RTOS shall provide a mechanism to define and initialize a semaphore at runtime.
- STATUS: Draft
- TYPE: Functional
- COMPONENT: Semaphore
- Parent -> ZEP-SYRS-14

## ZEP-SRS-5-3: Maximum limit of a semaphore (REQUIREMENT)
The Zephyr RTOS shall define the maximum limit of a semaphore when the semaphore is used for counting purposes and does not have an explicit limit.
- STATUS: Draft
- TYPE: Functional
- COMPONENT: Semaphore

## ZEP-SRS-5-4: Initialialization with maximum count value (REQUIREMENT)
When initializing a counting semaphore, the maximum permitted count a semaphore
can have shall be set.
- STATUS: Draft
- TYPE: Functional
- COMPONENT: Semaphore
- Parent -> ZEP-SYRS-14

## ZEP-SRS-5-5: Initial semaphore value (REQUIREMENT)
When initializing a counting semaphore, the initial semaphore value shall be set.
- STATUS: Draft
- TYPE: Functional
- COMPONENT: Semaphore
- Parent -> ZEP-SYRS-14

## ZEP-SRS-5-6: Semaphore acquisition mechanism (REQUIREMENT)
The Zephyr RTOS shall provide a mechanism allowing threads to acquire a semaphore.
- STATUS: Draft
- TYPE: Functional
- COMPONENT: Semaphore
- Parent -> ZEP-SYRS-14

## ZEP-SRS-5-7: Semaphore acquisition with count greater than zero (REQUIREMENT)
While the semaphore's count is greater than zero, the requesting thread shall acquire
the semaphore and decrement its count.
- STATUS: Draft
- TYPE: Functional
- COMPONENT: Semaphore
- Parent -> ZEP-SYRS-14

## ZEP-SRS-5-8: Semaphore acquisition with zero count (REQUIREMENT)
While the semaphore's count is zero, the requesting thread shall be blocked until the semaphore is released by another thread.
- STATUS: Draft
- TYPE: Functional
- COMPONENT: Semaphore
- Parent -> ZEP-SYRS-14

## ZEP-SRS-5-9: Semaphore acquisition timeout (REQUIREMENT)
When attempting to acquire a semaphore, the Zephyr RTOS shall accept options that specify timeout periods, allowing threads to set a maximum wait time for semaphore acquisition.
- STATUS: Draft
- TYPE: Functional
- COMPONENT: Semaphore
- Parent -> ZEP-SYRS-14

## ZEP-SRS-5-10: Semaphore acquisition timeout error handling (REQUIREMENT)
When attempting to acquire a semaphore, where the semaphore is not acquired within the
specified time, the Zephyr RTOS shall return an error indicating a timeout.
- STATUS: Draft
- TYPE: Functional
- COMPONENT: Semaphore
- Parent -> ZEP-SYRS-14

## ZEP-SRS-5-11: Semaphore acquisition no wait error handling (REQUIREMENT)
When attempting to acquire a semaphore, where the current count is zero and no timeout time was provided, the Zephyr RTOS
shall return an error indicating the semaphore is busy.
- STATUS: Draft
- TYPE: Functional
- COMPONENT: Semaphore
- Parent -> ZEP-SYRS-14

## ZEP-SRS-5-12: Semaphore release (REQUIREMENT)
The Zephyr RTOS shall provide a mechanism allowing threads to release a semaphore.
- STATUS: Draft
- TYPE: Functional
- COMPONENT: Semaphore
- Parent -> ZEP-SYRS-14

## ZEP-SRS-5-13: Semaphore release (REQUIREMENT)
The Zephyr RTOS shall increment the semaphore's count upon release.
- STATUS: Draft
- TYPE: Functional
- COMPONENT: Semaphore
- Parent -> ZEP-SYRS-14

## ZEP-SRS-5-14: Semaphore release with priority inheritance (REQUIREMENT)
When there are threads waiting on the semaphore, the highest-priority waiting thread
shall be unblocked and acquire the semaphore.
- STATUS: Draft
- TYPE: Functional
- COMPONENT: Semaphore
- Parent -> ZEP-SYRS-14

## ZEP-SRS-5-15: Checking semaphore count (REQUIREMENT)
The Zephyr RTOS shall provide a mechanism for threads to check the current count of a semaphore without acquiring it.
- STATUS: Draft
- TYPE: Functional
- COMPONENT: Semaphore
- Parent -> ZEP-SYRS-14

## ZEP-SRS-5-16: Semaphore reset (REQUIREMENT)
The Zephyr RTOS shall provide a mechanism that resets the semaphore count to zero.
- STATUS: Draft
- TYPE: Functional
- COMPONENT: Semaphore
- Parent -> ZEP-SYRS-14

## ZEP-SRS-5-17: Semaphore acquisitions abort after reset (REQUIREMENT)
When a semaphore is reset, the Zephyr RTOS shall abort all existing acquisitions
of the semaphore returning a resource contention error code.
- STATUS: Draft
- TYPE: Functional
- COMPONENT: Semaphore
- Parent -> ZEP-SYRS-14

## ZEP-SRS-5-18: Semaphore Initialization Option Validation (REQUIREMENT)
When initializing a counting semaphore, where the maximum permitted count of a semaphore is invalid,
then the Zephyr RTOS shall return an error indicating invalid values.
- STATUS: Draft
- TYPE: Functional
- COMPONENT: Semaphore
- Parent -> ZEP-SYRS-14

# Specification: System Initialization

## R164 (TEXT)
SPDX-License-Identifier: Apache-2.0

## R165 (TEXT)
TBD

# Specification: Thread Communication

## R166 (TEXT)
SPDX-License-Identifier: Apache-2.0

## ZEP-SRS-3-1: Exchanging data between threads (REQUIREMENT)
The Zephyr RTOS shall provide a mechanism for exchanging data between threads.
- STATUS: Draft
- TYPE: Functional
- COMPONENT: Thread Communication
- USER_STORY: (Note: copying data may be needed here - what is Zephyr doing? is it configurable?)

## ZEP-SRS-3-2: Waiting for results during communication (REQUIREMENT)
The Zephyr RTOS shall provide mechanisms to enable waiting for results during communication between threads. (NOTE:  waiting for results is really bad and dangerous, want to avoid if at all possible).
- STATUS: Draft
- TYPE: Functional
- COMPONENT: Thread Communication
- USER_STORY: =N73

## ZEP-SRS-3-3: Poll Operation Support (REQUIREMENT)
The Zephyr RTOS shall support a poll operation which enables waiting concurrently for any one of multiple conditions to be fulfilled.
- STATUS: Draft
- TYPE: Functional
- COMPONENT: Thread Communication
- USER_STORY: As a Zephyr RTOS user I want my thread to wait for one of several defined events to occur and only continue when one of them has occurred.

## ZEP-SRS-3-4: Pipe Communication Primitive (REQUIREMENT)
The Zephyr RTOS shall provide a communication primitive that allows a thread to transfer a block of
data to another thread.
- STATUS: Draft
- TYPE: Functional
- COMPONENT: Thread Communication
- USER_STORY: As a Zephyr RTOS user I want to send a byte stream from one thread to another in a thread-safe manner.

## ZEP-SRS-3-5: Message Queue (REQUIREMENT)
The Zephyr RTOS shall provide a a communication primitive that allow threads and ISRs to asynchronously exchange fixed-size data items.
- STATUS: Draft
- TYPE: Functional
- COMPONENT: Thread Communication

## ZEP-SRS-3-6: Mailbox Kernel Primitive (REQUIREMENT)
The Zephyr RTOS shall provide a communication primitive that allows threads to exchange messages of varying sizes asynchronously or synchronously.
- STATUS: Draft
- TYPE: Functional
- COMPONENT: Thread Communication
- USER_STORY: As a Zephyr RTOS user I want a sending thread to deposit a message into the mailbox,
  and a receiving thread to be able to retrieve the message at its convenience. This
  allows for asynchronous communication, where threads do not need to synchronize their
  execution explicitly.

# Specification: Thread Scheduling

## R173 (TEXT)
SPDX-License-Identifier: Apache-2.0

## R174: Thread Scheduling (SECTION)

### ZEP-SRS-2-1: Support operation on more than one CPU (REQUIREMENT)
The Zephyr RTOS shall support operation on more than one physical CPU sharing the same kernel state.
- STATUS: Draft
- TYPE: Functional
- COMPONENT: Multi Core

### ZEP-SRS-2-2: Running threads on specific CPUs (REQUIREMENT)
The Zephyr RTOS shall provide an interface for running threads on specific sets of CPUs ( default is 1 CPU).
- STATUS: Draft
- TYPE: Functional
- COMPONENT: Multi Core
- USER_STORY: As a Zephyr RTOS user I want Zephyr OS to be able to specify the CPU core or the set of CPU cores on which a thread shall be executed.

### ZEP-SRS-2-3: Exclusion between physical CPUs (REQUIREMENT)
The Zephyr RTOS shall provide an interface for mutual exclusion between multiple physical CPUs.
- STATUS: Draft
- TYPE: Functional
- COMPONENT: Multi Core
- USER_STORY: As a Zephyr RTOS user I want Zephyr OS to provide synchronization mechanisms between the CPU cores and the access to common resources.

## R178: Thread Scheduling (SECTION)

### ZEP-SRS-2-4: Scheduling a thread based on an event (REQUIREMENT)
The Zephyr RTOS shall provide an interface to schedule a thread based on an event.
- STATUS: Draft
- TYPE: Functional
- COMPONENT: Thread Scheduling
- USER_STORY: As a Zephyr RTOS user, I want to be able to execute work which reacts on events and interrupts the current executed work.
- Parent -> ZEP-SYRS-15

### ZEP-SRS-2-5: Deadline Scheduling Priorities (REQUIREMENT)
The Zephyr RTOS shall organize running threads by earliest deadline first priority.
- STATUS: Draft
- TYPE: Functional
- COMPONENT: Thread Scheduling
- USER_STORY: As a Zephyr RTOS user, I want to be able to schedule threads by earliest deadline first.

### ZEP-SRS-2-6: Work Queue utility capable of running preemptible work items (REQUIREMENT)
The Zephyr RTOS shall provide a thread-pooled work queue utility capable of running preemptible work items with specific scheduler priorities.
- STATUS: Draft
- TYPE: Functional
- COMPONENT: Thread Scheduling
- USER_STORY: As a Zephyr RTOS user, I want to be able to add work items in a thread work queue with different priorities and these shall be scheduled according their priorities.

### ZEP-SRS-2-7: Run user supplied functions in-order in a separate thread(s) (REQUIREMENT)
The Zephyr RTOS shall provide an interface for running user-supplied functions.
- STATUS: Draft
- TYPE: Functional
- COMPONENT: Thread Scheduling
- USER_STORY: As a Zephyr RTOS user, I want to be able to run functions in-order in a separated thread/threads.

### ZEP-SRS-2-8: Organize running threads into a fixed list (REQUIREMENT)
The Zephyr RTOS shall organize running threads into a fixed list of numeric priorities.
- STATUS: Draft
- TYPE: Functional
- COMPONENT: Thread Scheduling
- USER_STORY: As a Zephyr RTOS user, I want that the OS organize running threads in a fixed list of numeric priorities.

### ZEP-SRS-2-9: Preemption support (REQUIREMENT)
The Zephyr RTOS shall support preemption of a running thread by a higher priority thread.
- STATUS: Draft
- TYPE: Functional
- COMPONENT: Thread Scheduling
- USER_STORY: As a Zephyr RTOS user, I want that the OS preempt running threads by a thread with higher priority.

### ZEP-SRS-2-10: Un-preemptible thread priorities (REQUIREMENT)
The Zephyr RTOS shall support thread priorities which cannot be preempted by other user threads.
- STATUS: Draft
- TYPE: Functional
- COMPONENT: Thread Scheduling
- USER_STORY: As a Zephyr RTOS user, I want to be able to configure thread prioritizes which cannot be preempted by other user threads.

### ZEP-SRS-2-11: Time sharing of CPU resources (REQUIREMENT)
The Zephyr RTOS shall support time sharing of CPU resources among threads of the same priority.
- STATUS: Draft
- TYPE: Functional
- COMPONENT: Thread Scheduling
- USER_STORY: As a Zephyr RTOS user, I want to be able to configure my RTOS in the way, that the CPU resources are shared evenly among executed threads of the same priority.

# Specification: Threads

## R187 (TEXT)
SPDX-License-Identifier: Apache-2.0

## ZEP-SRS-1-1: Creating threads (REQUIREMENT)
The Zephyr RTOS shall provide an interface to create (start) a thread.
- STATUS: Draft
- TYPE: Functional
- COMPONENT: Threads
- Parent -> ZEP-SYRS-15
- Parent -> ZEP-SYRS-16

## ZEP-SRS-1-2: Setting thread priority (REQUIREMENT)
The Zephyr RTOS shall provide an interface to set a thread's priority.
- STATUS: Draft
- TYPE: Functional
- COMPONENT: Threads
- Parent -> ZEP-SYRS-17

## ZEP-SRS-1-3: Suspending a thread (REQUIREMENT)
The Zephyr RTOS shall provide an interface to suspend a thread.
- STATUS: Draft
- TYPE: Functional
- COMPONENT: Threads
- Parent -> ZEP-SYRS-15
- Parent -> ZEP-SYRS-16

## ZEP-SRS-1-4: Resuming a suspended thread (REQUIREMENT)
The Zephyr RTOS shall provide an interface to resume a suspended thread.
- STATUS: Draft
- TYPE: Functional
- COMPONENT: Threads
- Parent -> ZEP-SYRS-15
- Parent -> ZEP-SYRS-16

## ZEP-SRS-1-5: Resuming a suspended thread after a timeout (REQUIREMENT)
The Zephyr RTOS shall provide an interface to resume a suspended thread after a timeout.
- STATUS: Draft
- TYPE: Functional
- COMPONENT: Threads
- Parent -> ZEP-SYRS-15
- Parent -> ZEP-SYRS-16

## ZEP-SRS-1-6: Deleting a thread (REQUIREMENT)
The Zephyr RTOS shall provide an interface to delete (end) a thread.
- STATUS: Draft
- TYPE: Functional
- COMPONENT: Threads
- Parent -> ZEP-SYRS-15
- Parent -> ZEP-SYRS-16

## ZEP-SRS-1-7: Thread states (REQUIREMENT)
Threads shall have different states to fulfill the Life-cycle of a thread
- STATUS: Draft
- TYPE: Functional
- COMPONENT: Threads
- USER_STORY: As a Zephyr RTOS user, I want to know in what state a specific thread is.
- Parent -> ZEP-SYRS-15
- Parent -> ZEP-SYRS-16

## ZEP-SRS-1-8: Thread stack objects (REQUIREMENT)
Every Thread shall have it's own stack.
- STATUS: Draft
- TYPE: Functional
- COMPONENT: Threads
- USER_STORY: As a Zephyr RTOS user I want to be able to configure the stack size of a thread. And every thread shall have it's own dedicated stack.
- Parent -> ZEP-SYRS-15
- Parent -> ZEP-SYRS-16

## ZEP-SRS-1-9: Thread privileges (REQUIREMENT)
The Zephyr RTOS shall provide an interface to create threads with defined privilege.
- STATUS: Draft
- TYPE: Functional
- COMPONENT: Threads
- Parent -> ZEP-SYRS-15
- Parent -> ZEP-SYRS-16

## ZEP-SRS-1-10: Scheduling multiple threads (REQUIREMENT)
The Zephyr RTOS shall provide an interface to schedule multiple threads.
- STATUS: Draft
- TYPE: Functional
- COMPONENT: Threads
- Parent -> ZEP-SYRS-16

## ZEP-SRS-1-11: Thread Options (REQUIREMENT)
The Zephyr RTOS shall support a set of thread options.
- STATUS: Draft
- TYPE: Functional
- COMPONENT: Threads
- USER_STORY: As a Zephyr RTOS user, I want to be able to pass specific option to a thread.
- Parent -> ZEP-SYRS-15
- Parent -> ZEP-SYRS-16

## ZEP-SRS-1-12: Thread Custom Data (REQUIREMENT)
Every thread shall have a custom data area.
- STATUS: Draft
- TYPE: Functional
- COMPONENT: Threads
- USER_STORY: As a Zephyr RTOS user, I want to be able to set a thread specific custom area for every thread I create and which can be used only by the thread itself or the can be used by the application
- Parent -> ZEP-SYRS-15
- Parent -> ZEP-SYRS-16

# Specification: Timers

## R200 (TEXT)
SPDX-License-Identifier: Apache-2.0

## ZEP-SRS-4-1: Timer definition at compile time (REQUIREMENT)
The Zephyr RTOS shall provide a mechanism to define and statically (i.e. compile time) initialize timers.
- STATUS: Draft
- TYPE: Functional
- COMPONENT: Timers
- Parent -> ZEP-SYRS-18

## ZEP-SRS-4-2: Timer expiry function (REQUIREMENT)
When initializing a timer, the Zephyr RTOS shall support setting a function that gets called when the timer expires.
- STATUS: Draft
- TYPE: Functional
- COMPONENT: Timers
- Parent -> ZEP-SYRS-18

## ZEP-SRS-4-3: Timer stop function (REQUIREMENT)
When initializing a timer, the Zephyr RTOS shall support setting a function that gets called when a running timer is stopped.
- STATUS: Draft
- TYPE: Functional
- COMPONENT: Timers
- Parent -> ZEP-SYRS-18

## ZEP-SRS-4-4: Timer definition at run time (REQUIREMENT)
The Zephyr RTOS shall provide a mechanism to define and initialize timers at run time.
- STATUS: Draft
- TYPE: Functional
- COMPONENT: Timers
- Parent -> ZEP-SYRS-18

## ZEP-SRS-4-5: Timer start (REQUIREMENT)
The Zephyr RTOS shall provide a mechanism to start a timer for a specific duration and periodicity.
- STATUS: Draft
- TYPE: Functional
- COMPONENT: Timers
- Parent -> ZEP-SYRS-18

## ZEP-SRS-4-6: Timer stop (REQUIREMENT)
The Zephyr RTOS shall provide a mechanism to stop a running timer.
- STATUS: Draft
- TYPE: Functional
- COMPONENT: Timers
- Parent -> ZEP-SYRS-18

## ZEP-SRS-4-7: Timer status (REQUIREMENT)
The Zephyr RTOS shall provide a mechanism to read the number of times a timer has expired and then reset this number to 0.
- STATUS: Draft
- TYPE: Non-Functional
- COMPONENT: Timers
- Parent -> ZEP-SYRS-18

## ZEP-SRS-4-8: Timer status reinitialization (REQUIREMENT)
When a timer is initialized, started or synchronized to a thread, the Zephyr RTOS shall reset the timer number of times it has expired to 0.
- STATUS: Draft
- TYPE: Non-Functional
- COMPONENT: Timers
- Parent -> ZEP-SYRS-18

## ZEP-SRS-4-9: Timer thread synchronization (REQUIREMENT)
The Zephyr RTOS shall provide a mechanism to synchronize a thread to a timer and then block the thread execution until any of the following conditions is satisfied:
- The timer is stopped
- The timer number of times it has expired is superior to 0
- STATUS: Draft
- TYPE: Functional
- COMPONENT: Timers
- Parent -> ZEP-SYRS-18

## ZEP-SRS-4-10: Timer next expiration time in system ticks (REQUIREMENT)
The Zephyr RTOS shall provide a mechanism to get a timer's next expiration time in system ticks.
- STATUS: Draft
- TYPE: Functional
- COMPONENT: Timers
- Parent -> ZEP-SYRS-18

## ZEP-SRS-4-11: Timer remaining time until expiration in system ticks (REQUIREMENT)
The Zephyr RTOS shall provide a mechanism to get a timer's remaining time until its next expiry in system ticks.
- STATUS: Draft
- TYPE: Functional
- COMPONENT: Timers
- Parent -> ZEP-SYRS-18

## ZEP-SRS-4-12: Timer remaining time until expiration in milliseconds (REQUIREMENT)
The Zephyr RTOS shall provide a mechanism to get the timer's remaining time until its next expiry in milliseconds.
- STATUS: Draft
- TYPE: Functional
- COMPONENT: Timers
- Parent -> ZEP-SYRS-18

## ZEP-SRS-4-13: Timer set user data (REQUIREMENT)
The Zephyr RTOS shall support adding user defined data to a timer.
- STATUS: Draft
- TYPE: Functional
- COMPONENT: Timers
- Parent -> ZEP-SYRS-18

## ZEP-SRS-4-14: Timer get user data (REQUIREMENT)
The Zephyr RTOS shall support retrieving user defined data from a timer.
- STATUS: Draft
- TYPE: Functional
- COMPONENT: Timers
- Parent -> ZEP-SYRS-18

## ZEP-SRS-4-15: Timer expire functions in interrupt context (REQUIREMENT)
When a timer expiry function is called, the Zephyr RTOS shall do so in the interrupt context.
- STATUS: Draft
- TYPE: Functional
- COMPONENT: Timers
- Parent -> ZEP-SYRS-18

# Specification: Tracing

## R216 (TEXT)
SPDX-License-Identifier: Apache-2.0

## ZEP-SRS-10-1: Initializing a trace (REQUIREMENT)
Zephyr shall provide an interface to initialize a trace.
- STATUS: Draft
- TYPE: Functional
- COMPONENT: Tracing

## ZEP-SRS-10-2: Triggering a trace (REQUIREMENT)
Zephyr shall provide an interface to trigger a trace.
- STATUS: Draft
- TYPE: Functional
- COMPONENT: Tracing

## ZEP-SRS-10-3: Dumping trace results (REQUIREMENT)
Zephyr shall provide an interface to dump results from a trace.
- STATUS: Draft
- TYPE: Functional
- COMPONENT: Tracing

## ZEP-SRS-10-4: Removing trace data (REQUIREMENT)
Zephyr shall provide an interface to remove trace data.
- STATUS: Draft
- TYPE: Functional
- COMPONENT: Tracing

## ZEP-SRS-10-5: Tracing Object Identification (REQUIREMENT)
Zephyr shall provide an interface to identify the objects being traced.
- STATUS: Draft
- TYPE: Functional
- COMPONENT: Tracing
- USER_STORY: As a Zepyhr OS user, I want to be able to give each object which I create a name / label in order to be able to identify them in a trace log.

## ZEP-SRS-10-6: Tracing Non-Interference (REQUIREMENT)
Zepyhr shall prevent the tracing functionality from interfering with normal operations.
- STATUS: Draft
- TYPE: Functional
- COMPONENT: Tracing
- USER_STORY: As a Zepyhr OS user, I want that the trace functionality do not interfere or slow down the operation system functionality.

# Specification: Zephyr System Requirements

## R223 (TEXT)
SPDX-License-Identifier: Apache-2.0

## ZEP-SYRS-1: Architecture Layer Interface (REQUIREMENT)
The Zephyr RTOS shall provide a framework to communicate with a set of hardware architectural services.
- STATUS: Draft
- TYPE: Functional
- COMPONENT: Hardware Architecture Interface
- USER_STORY: As a Zephyr RTOS user I want to be able to easily switch my application to a different MCU architecture (x86, ARM Cortex-M/A, RISCV etc.).

## ZEP-SYRS-2: Support multiprocessor management (REQUIREMENT)
The Zephyr RTOS shall support symmetric multiprocessing on multiple cores.
- STATUS: Draft
- TYPE: Functional
- COMPONENT: Hardware Architecture Interface
- USER_STORY: As a Zephyr RTOS user I want to use Zephyr OS on multi core (SMP-)MCUs/MPUs.
- Parent -> ZEP-SYRS-1

## ZEP-SYRS-3: Support Subset of Standard C Library (REQUIREMENT)
The Zephyr RTOS shall support a subset of the standard C library.
- STATUS: Draft
- TYPE: Functional
- COMPONENT: C Library
- USER_STORY: As a Zephyr RTOS user I want to have a selection of standard C library implementations e.g. a full extend and a minimal with a smaller footprint or a particular fast executing implementation.

## ZEP-SYRS-4: Device Driver Abstraction (REQUIREMENT)
The Zephyr RTOS shall provide a framework for managing device drivers and peripherals.
- STATUS: Draft
- TYPE: Functional
- COMPONENT: Device Drivers
- USER_STORY: As a Zephyr RTOS user I want my application to be portable between different MCU architectures (ARM Cortex-M/A, Intel x86, RISCV etc.) and MCU vendors (STM, NXP, Intel, etc.) without having to change the MCU peripherals access.

## ZEP-SYRS-5: Fatal error and exception handling (REQUIREMENT)
The Zephyr RTOS shall provide a framework for error and exception handling.
- STATUS: Draft
- TYPE: Functional
- COMPONENT: Exception and Error Handling
- USER_STORY: As a Zephyr RTOS user I want errors and exceptions to handled and react according to my applications requirements (e.g. reach/establish the applications safety state).

## ZEP-SYRS-6: Common File system operation support (REQUIREMENT)
The Zephyr RTOS shall provide a framework for managing file system access.
- STATUS: Draft
- TYPE: Functional
- COMPONENT: File Systems
- USER_STORY: As a Zephyr RTOS user I want a posix / c like file system access to store data.

## ZEP-SYRS-7: Interrupt Management (REQUIREMENT)
The Zephyr RTOS shall provide a framework for interrupt and interrupt service routine management.
- STATUS: Draft
- TYPE: Functional
- COMPONENT: Interrupts
- USER_STORY: As the Zephyr RTOS user I want the Kernel to provide abstracted interfaces to
  the platform enabling me to implement standard interrupts interrupt service routines
  without detailed knowledge of the platform architecture and programming model.

## ZEP-SYRS-20: Direct ISR, Platform Specific helpers. (REQUIREMENT)
Zephyr RTOS shall support development of direct ISRs by providing platform specific
code fragments and factory functions including, minimal header instructions,
minimal footer instructions, low power termination, and ISR construction.
- STATUS: Draft
- TYPE: Functional
- COMPONENT: Interrupts
- USER_STORY: As the Zephyr RTOS user I want the Kernel to provide support for implementing standard low latency
  and low power interrupt service routines without detailed knowledge of the platform architecture
  and programming model.
- Parent -> ZEP-SYRS-7

## ZEP-SYRS-8: Logging (REQUIREMENT)
The Zephyr RTOS shall provide a framework for logging events.
- STATUS: Draft
- TYPE: Functional
- USER_STORY: As a Zephyr RTOS user I want to be able to log application defined events as well as framework exceptions.

## ZEP-SYRS-9: Memory Management framework (REQUIREMENT)
The Zephyr RTOS shall support a memory management framework.
- STATUS: Draft
- TYPE: Functional
- COMPONENT: Memory Management
- USER_STORY: As a Zephyr RTOS user I want memory to be allocated and protected to my application threads preventing mistakenly access to foreign memory as far as the hardware allows.

## ZEP-SYRS-10: Power Management (REQUIREMENT)
The Zephyr RTOS shall provide an interface to control hardware power states.
- STATUS: Draft
- TYPE: Functional
- USER_STORY: As a Zephyr RTOS user I want to be able to control the power mode of the MCU and its peripherals to take advantage of the hardware features and to be able to implement low power or battery driven long life applications.

## R235: Multi core and SMP (SECTION)

### ZEP-SYRS-11: Multiple CPU scheduling (REQUIREMENT)
The Zephyr RTOS shall support scheduling of threads on multiple hardware CPUs.
- STATUS: Draft
- TYPE: Functional
- COMPONENT: SMP and Multi core
- USER_STORY: As a Zephyr RTOS user I want Zephyr OS to run on MCUs/CPUs with one or more CPU cores.

### ZEP-SYRS-12: Scheduling (REQUIREMENT)
The Zephyr RTOS shall provide an interface to assign a thread to a specific CPU.
- STATUS: Draft
- TYPE: Functional
- COMPONENT: SMP and Multi core
- USER_STORY: As a Zephyr RTOS user, I want to be able to control which thread will run on which CPU.

## R238: Thread Synchronization (SECTION)

### ZEP-SYRS-13: Mutex (REQUIREMENT)
The Zephyr RTOS shall provide an interface for managing communication between threads.
- STATUS: Draft
- TYPE: Functional
- USER_STORY: As a Zephyr RTOS user I want to able to exchange information between threads in a thread-safe manner guaranteeing data consistence.

### ZEP-SYRS-14: Counting Semaphore (REQUIREMENT)
The system shall implement a semaphore synchronization primitive for coordinating access to shared resources among multiple threads.
- STATUS: Draft
- TYPE: Functional
- COMPONENT: Semaphore

## R241: Threads (SECTION)

### ZEP-SYRS-15: Thread support (REQUIREMENT)
The Zephyr RTOS shall support threads.
- STATUS: Draft
- TYPE: Functional
- COMPONENT: Threads
- USER_STORY: As a Zephyr RTOS user, I want to be able to have support for the kernel objects named threads for processing work.

### ZEP-SYRS-16: Thread management (REQUIREMENT)
The Zephyr RTOS shall provide a framework for managing multiple threads of execution.
- STATUS: Draft
- TYPE: Functional
- COMPONENT: Threads
- USER_STORY: As a Zephyr RTOS user, I want to be able to manage the execute of multiple threads with different priorities.

### ZEP-SYRS-17: Thread priority (REQUIREMENT)
Threads shall have a priority.
- STATUS: Draft
- TYPE: Functional
- COMPONENT: Threads
- USER_STORY: As a Zephyr RTOS user, I want to be able to give my threads different priorities for execution.

## ZEP-SYRS-18: Timers (REQUIREMENT)
The Zephyr RTOS shall provide a framework for managing time-based events.
- STATUS: Draft
- TYPE: Functional
- USER_STORY: As a Zephyr RTOS user, I want to start, suspend, resume and stop timers which shall trigger an event on a set expiration time.

## ZEP-SYRS-19: Tracing (REQUIREMENT)
Zepyhr shall provide a framework mechanism for tracing low level system operations  (NOTE: system calls, interrupts, kernel calls, thread, synchronization, etc.).
- STATUS: Draft
- TYPE: Functional
- USER_STORY: As a Zephyr RTOS user, I want to be able to trace different OS operations.

## R247: Condition Variables (SECTION)

### ZEP-SYRS-21: Condition Variables (REQUIREMENT)
The Zephyr RTOS shall provide a framework to synchronize threads based on a condition variable.
- STATUS: Draft
- TYPE: Non-Functional

## R249: Queues (SECTION)

### ZEP-SYRS-22: Queues data passing (REQUIREMENT)
The Zephyr RTOS shall implement a queue which can be used to pass data between threads and interrupt service routines.
- STATUS: Draft
- TYPE: Functional
- COMPONENT: Queues

## R251: LIFOs (SECTION)

### ZEP-SYRS-23: LIFOs data passing (REQUIREMENT)
The Zephyr RTOS shall implement a LIFOs which can be used to pass data between threads and interrupt service routines.
- STATUS: Draft
- TYPE: Functional
- COMPONENT: LIFOs

## R253: FIFOs (SECTION)

### ZEP-SYRS-24: FIFOs data passing (REQUIREMENT)
The Zephyr RTOS shall implement FIFOs which can be used to pass data between threads and interrupt service routines.
- STATUS: Draft
- TYPE: Functional
- COMPONENT: FIFOs

## R255: Mailboxes (SECTION)

### ZEP-SYRS-25: Mailboxes (REQUIREMENT)
The Zephyr RTOS shall provide a framework to pass messages of arbitrary size between threads.
- STATUS: Draft
- TYPE: Functional
